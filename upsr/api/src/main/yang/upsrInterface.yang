module upsrInterface {
    yang-version 1;
    namespace "urn:opendaylight:params:xml:ns:yang:upsrInterface";
    prefix "upsrInterface";

    revision "2018-11-19" {
        description "Initial revision of upsrInterface model";
    }
    grouping InterfaceInfo
    {
        leaf ifnetName { type string; }
        leaf ifnetIP { type string; }
        leaf ifnetMask { type string; }
        leaf ifnetMac { type string; }
        leaf vpnName { type string; }
        leaf adjLabel { type string; }
        leaf ifnetStatus { type string; }
        leaf srStatus { type string; }
        leaf linkStatus { type string; }
        leaf runningStatus { type string; }
    }
    grouping InterfaceListInfo {
        list devInterfaces {
            uses InterfaceInfo;
        }
    }
    rpc getInterfaces {
        input {
            leaf routerId { type string; }
        }
        output {
            leaf result { type string; }
            uses InterfaceListInfo;
        }
    }
}
