module upsrStatistic {
    yang-version 1;
    namespace "urn:opendaylight:params:xml:ns:yang:upsrStatistic";
    prefix "upsrStatistic";

    revision "2018-12-27" {
        description "Initial revision of upsrStatistic model";
    }

    grouping statistic{
        leaf ifIndex { type string; }
        leaf ifName { type string; }
        leaf routerId { type string; }
        leaf date { type string; }
        leaf rcvUniPacket { type string; }
        leaf sendUniPacket { type string; }
        leaf sendPacket { type string; }
        leaf inPacketRate { type string; }
        leaf outPacketRate { type string; }
        leaf inUseRate { type string; }
        leaf outUseRate { type string; }
        leaf rcvErrorPacket { type string; }
        leaf sendErrorPacket { type string; }
    }
    grouping ifClearedStatGroup{
        leaf routerId { type string; }
        list ifCleared {
            leaf ifIndex { type string; }
            leaf ifName { type string; }
            leaf date { type string; }
            leaf rcvUniPacket { type string; }
            leaf sendUniPacket { type string; }
            leaf inPacketRate { type string; }
            leaf outPacketRate { type string; }
            leaf inUseRate { type string; }
            leaf outUseRate { type string; }
            leaf rcvErrorPacket { type string; }
            leaf sendErrorPacket { type string; }
            leaf vpnName { type string; }
        }
    }
    grouping ifStatisticsGroup{
        leaf routerId { type string; }
        list ifStatistics {
            leaf ifIndex { type string; }
            leaf ifName { type string; }
            leaf date { type string; }
            leaf rcvUniPacket { type string; }
            leaf sendUniPacket { type string; }
        }
    }
    grouping cpuInfoGroup{
        leaf routerId { type string; }
        list cpuInfo {
            leaf position { type string; }
            leaf entIndex { type string; }
            leaf systemCpuUsage { type string; }
            leaf ovloadThreshold { type string; }
            leaf unovloadThreshold { type string; }
            leaf date { type string; }
        }
    }
    grouping memoryInfoGroup{
        leaf routerId { type string; }
        list memoryInfo {
            leaf position { type string; }
            leaf entIndex { type string; }
            leaf osMemoryTotal { type string; }
            leaf osMemoryUse { type string; }
            leaf osMemoryUsage { type string; }
            leaf date { type string; }
        }
    }
    grouping memoryInfoStatList {
        list memoryInfoStat {
            uses memoryInfoGroup;
        }
    }
    grouping cpuInfoStatList {
        list cpuInfoStat {
            uses cpuInfoGroup;
        }
    }
    grouping routerIfClearedList {
        list routerIfCleared {
            uses ifClearedStatGroup;
        }
    }
    rpc getStatistic {
        input {
            leaf routerId { type string; }
            leaf type { type string; }
        }
        output {
            leaf result { type string; }
            list statistics {
                uses statistic;
            }
        }
    }

    rpc getIfClearedStat {
        input {
            leaf routerId { type string; }
        }
        output {
            leaf result { type string; }
            uses routerIfClearedList;
        }
    }
    rpc getIfStatistics {
        input {
            leaf routerId { type string; }
        }
        output {
            leaf result { type string; }
            list routerIfStatistics {
                uses ifStatisticsGroup;
            }
        }
    }
    rpc getCpuInfo {
        input {
            leaf routerId { type string; }
        }
        output {
            leaf result { type string; }
            uses cpuInfoStatList;
        }
    }
    rpc getMemoryInfo {
        input {
            leaf routerId { type string; }
        }
        output {
            leaf result { type string; }
            uses memoryInfoStatList;
        }
    }
    rpc updateStatisticSwitch {
        input {
            leaf switchValue { type string; }
            leaf statisticInterval { type string; }
        }
        output {
            leaf result { type string; }
        }
    }

    rpc getStatisticSwitch {
        input {
        }
        output {
            leaf result { type string; }
            leaf switchValue { type string; }
            leaf statisticInterval { type string; }
        }
    }
    rpc getStatisticHistory {
        input {
            leaf routerId { type string; }
            leaf historyNum { type string; }
            leaf tunnelName { type string; }
            leaf vpnName { type string; }
        }
        output {
            leaf result { type string; }
            list ifClearedHistory {
                leaf historyIndex { type string; }
                uses routerIfClearedList;
            }
            list cpuInfoHistory {
                leaf historyIndex { type string; }
                uses cpuInfoStatList;
            }
            list memoryInfoHistory {
                leaf historyIndex { type string; }
                uses memoryInfoStatList;
            }
        }
    }
}
