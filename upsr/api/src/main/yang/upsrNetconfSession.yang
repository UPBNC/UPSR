module upsrNetconfSession {
    yang-version 1;
    namespace "urn:opendaylight:params:xml:ns:yang:upsrNetconfSession";
    prefix "upsrNetconfSession";

    revision "2018-11-19" {
        description "Initial revision of upsrNetconfSession model";
    }
    grouping netconfInfo
    {
        leaf sshIp { type string; }
        leaf sshPort { type int32; }
        leaf userName { type string; }
        leaf password { type string; }
    }
    grouping devNetconfInfo
    {
        leaf deviceName { type string; }
        leaf centerName { type string; }
        leaf deviceType { type string; }
        leaf routerId { type string; }
        uses netconfInfo;
    }
    rpc getAllNetconf {
        output {
            leaf result { type string; }
            list devices {
                uses devNetconfInfo;
                leaf sysName { type string; }
                leaf connectStatus { type string; }
            }
        }
    }
    rpc getNetconf {
        input {
            leaf routerId { type string; }
        }
        output {
            leaf result { type string; }
            uses devNetconfInfo;
            leaf sysName { type string; }
            leaf connectStatus { type string; }
        }
    }
    rpc delNetconf
    {
        input {
            leaf routerId { type string; }
        }
        output {
            leaf result { type string; }
        }
    }
    rpc updateNetconf
    {
        input {
            uses devNetconfInfo;
        }
        output {
            leaf result { type string; }
        }
    }
    rpc actConnect {
        input {
            leaf routerId { type string; }
            leaf action { type string; }
        }
        output {
            leaf result { type string; }
        }
    }
}
