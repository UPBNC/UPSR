module upsrSyncConf {
    yang-version 1;
    namespace "urn:opendaylight:params:xml:ns:yang:upsrSyncConf";
    prefix "upsrSyncConf";

    revision "2018-11-29" {
        description "Initial revision of upsrSyncConf model";
    }
    rpc syncConf {
        input {
            leaf syncType { type string; }
        }
        output {
            leaf result {
                type string;
            }
        }
    }
}
