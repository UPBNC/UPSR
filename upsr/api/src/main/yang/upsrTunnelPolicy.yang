module upsrTunnelPolicy {
    yang-version 1.1;
    namespace "urn:opendaylight:params:xml:ns:yang:upsrTunnelPolicy";
    prefix "upsrTunnelPolicy";

    revision "2012-02-22" { // TODO change revision to date of model creation
        description "Initial revision of upsrTunnelPolicy model";
    }

    grouping tunnelPolicy {
        leaf policyName { type string; }
        leaf description{type string;}
        leaf tnlPolicyType{type string;}
        list tpNexthops {
            leaf destAddr { type string; }
            leaf ignoreDestCheck { type string; }
            leaf includeLdp { type string; }
            leaf downSwitch { type string; }
            list bindTunnel {
                leaf tunnelName { type string; }
            }
        }
        list tnlSelSeqs{
            leaf loadBalanceNum { type string; }
            leaf selTnlType1{type string;}
            leaf selTnlType2{type string;}
            leaf selTnlType3{type string;}
            leaf selTnlType4{type string;}
            leaf selTnlType5{type string;}
            leaf unmix{type string;}
        }
    }

    rpc getTunnelPolicys {
        input {
            leaf routerId { type string; }
            leaf policyName { type string; }
        }
        output {
            leaf result { type string; }
            list tunnelPolicys {
                leaf routerId{type string;}
                uses tunnelPolicy;
            }
        }
    }

    rpc updateTunnelPolicy {
        input {
            leaf routerId { type string; }
            uses tunnelPolicy;
        }
        output {
            leaf result { type string; }
        }
    }

    rpc deleteTunnelPolicy {
        input {
            leaf routerId { type string; }
            leaf policyName { type string; }
        }
        output {
            leaf result { type string; }
        }
    }
}
