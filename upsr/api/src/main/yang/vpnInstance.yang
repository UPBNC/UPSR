module vpnInstance {
    yang-version 1;
    namespace "urn:opendaylight:params:xml:ns:yang:vpnInstance";
    prefix "vpnInstance";

    revision "2018-11-19" {
        description "Initial revision of vpnInstance model";
    }
    rpc vpnInstance {
        input {
            leaf name {
                type string;
            }
        }
        output {
            leaf greeting {
                type string;
            }
        }
    }
    rpc vpnInstanceDel
    {
        input {
            leaf vpnName {
                type string;
            }
        }
        output {
            leaf result {
                type string;
            }
        }
    }
    rpc vpnInstanceUpdate
    {
        input {
            leaf vpnName {
                type string;
            }
            leaf bussRegion {
                type string;
            }
            leaf routeId {
                type string;
            }
            leaf import-RT {
                type string;
            }
            leaf export-RT {
                type string;
            }
            leaf peerAS {
                type int32;
            }
            leaf peerIP {
                type string;
            }
            leaf deviceIP {
                type string;
            }

        }
        output {
            leaf result {
                type string;
            }
        }
    }
    rpc vpnInstanceGet
    {
        input {
            leaf vpnName {
                type string;
            }
        }
        output {
            leaf result {
                type string;
            }
            leaf id {
                type int32;
            }
            leaf vpnName {
                type string;
            }
            leaf bussRegion {
                type string;
            }

            leaf routeId {
                type string;
            }
            leaf import-RT {
                type string;
            }
            leaf export-RT {
                type string;
            }
            leaf peerAS {
                type int32;
            }
            leaf peerIP {
                type string;
            }
        }
    }
}
