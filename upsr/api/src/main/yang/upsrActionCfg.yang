module upsrActionCfg {
    yang-version 1;
    namespace "urn:opendaylight:params:xml:ns:yang:upsrActionCfg";
    prefix "upsrActionCfg";

    revision "2019-05-09" {
        description "Initial revision of upsrActionCfg model";
    }

    grouping routers {
            list router{
                leaf routerId { type string; }
             }
    }
    rpc vpn {
        input {
            uses routers;
        }
        output {
            leaf result { type string; }
        }
    }


    rpc lable {
        input {
            uses routers;
        }
        output {
            leaf result { type string; }
        }
    }

    rpc tunnel {
        input {
            uses routers;
        }
        output {
            leaf result { type string; }
        }
    }

    rpc confirm {
        input {
            uses routers;
        }
        output {
            leaf result { type string; }
        }
    }

    rpc cancel {
        input {
            uses routers;
        }
        output {
            leaf result { type string; }
        }
    }

    rpc commitCfg {
             input {
                 leaf routerId { type string; }
                 leaf cfgType { type string; }
             }
             output {
                 leaf result { type string; }
             }
         }

    rpc getCfgCliChange {
        input {
            leaf routerId { type string; }
        }
        output {
            leaf result { type string; }
            list cliChanges {
                leaf routerId { type string; }
                list commandChanges{
                    leaf commandId { type string; }
                    leaf candidate { type string; }
                    leaf running { type string; }
                    leaf actionType { type string; }
                    leaf cliCommand { type string; }
                }
            }
        }
    }

    rpc getCfgChange {
        input {
            leaf routerId { type string; }
            leaf cfgType { type string; }
        }
        output {
            leaf result { type string; }
            list command {
                leaf routerId { type string; }
                leaf deviceName { type string; }
                list commandChange {
                    leaf index { type string; }
                    leaf change { type string; }
                }
            }
        }
    }

    rpc confirmCfgChange {
        input {
            leaf routerId { type string; }
            leaf cfgType { type string; }
        }
        output {
            leaf result { type string; }
        }
    }

    rpc cancelCfgChange {
        input {
            leaf routerId { type string; }
            leaf cfgType { type string; }
        }
        output {
            leaf result { type string; }
        }
    }

    rpc getCfgCommit {
        input {
            leaf routerId { type string; }
            leaf commitId { type string; }
            leaf isdetail { type string; }
        }
        output {
            leaf result { type string; }
            list commitRouters {
                leaf routerId { type string; }
                list commitInfo {
                    leaf commitId { type string; }
                    leaf userName { type string; }
                    leaf userLabel { type string; }
                    leaf timeStamp { type string; }
                    list currentChanges {
                        leaf index { type string; }
                        leaf change { type string; }
                    }
                    list sinceChanges {
                        leaf index { type string; }
                        leaf change { type string; }
                    }
                }
            }
        }
    }

    rpc rollback {
        input {
            leaf routerId { type string; }
            leaf commitId { type string; }
        }
        output {
            leaf result { type string; }
        }
    }
}
