module upsrBgplsSession {
    yang-version 1;
    namespace "urn:opendaylight:params:xml:ns:yang:upsrBgplsSession";
    prefix "upsrBgplsSession";

    revision "2018-11-20" {
        description "Initial revision of upsrBgplsSession model";
    }
    rpc addBgpls {
        input {
            leaf bgpIp { type string; }
            leaf bgpAs { type string; }
        }
        output {
            leaf retCode { type string; }
            leaf retMsg { type string; }
        }
    }
    rpc getBgpls {
        output {
            leaf sessionName { type string; }
            leaf bgpIp { type string; }
            leaf bgpAs { type string; }
            leaf bgpStatus { type string; }
        }
    }
    rpc delBgpls {
        input {
            leaf bgpIp { type string; }
        }
        output {
            leaf retCode { type string; }
            leaf retMsg { type string; }
        }
    }
}
