module upsrSrLabel {
    yang-version 1.1;
    namespace "urn:opendaylight:params:xml:ns:yang:upsrSrLabel";
    prefix "upsrSrLabel";

    revision "2018-11-26" {
        description "Initial revision of upsrSrLabel model";
    }

    grouping srGlobal {
        container srgbPrefixSid{
            leaf srgbBegin { type string; }
            leaf srgbEnd { type string; }
            leaf prefixId { type string; }
            leaf adjBegin { type string; }
            leaf adjEnd { type string; }
            list srgbRange {
                leaf srgbBegin { type int32; }
                leaf srgbEnd { type int32; }
            }
        }
    }
    grouping srInterface {
        leaf ifAddress { type string; }
        leaf ifNetMask { type string; }
        leaf ifName { type string; }
        leaf srEnabled { type string; }
        leaf adjlabel { type string; }
        leaf phyStatus{type string;}
        leaf isSrDomain { type string; }
        leaf vpnBind { type string; }
        leaf trunkName { type string; }
    }
    grouping srgbLabelInfo {
        leaf routerId { type string; }
        leaf srEnabled { type string; }
        uses srGlobal;
    }
    grouping intfLabelInfo {
        leaf routerId { type string; }
        leaf intfLocalAddress { type string; }
        leaf intfRemoteAddress { type string; }
        leaf intfLabelVal { type string; }
        uses srInterface;
    }
    rpc updateSrgbLabel {
        input {
        //    uses srgbLabelInfo;
        }
        output {
        //    leaf result { type string; }
        }
    }
    rpc getSrgbLabel {
        input {
            leaf routerId { type string; }
        }
        output {
            leaf result { type string; }
            uses srgbLabelInfo;
        }
    }
    rpc updateIntfLabel {
        input {
        //    uses intfLabelInfo;
        }
        output {
        //    leaf result { type string; }
        }
    }
    rpc getIntfLabel {
        input {
            leaf routerId { type string; }
            leaf intfLocalAddress { type string; }
        }
        output {
            leaf result { type string; }
            uses intfLabelInfo;
        }
    }
    rpc updateSrLabel {
        input {
        //    uses srgbLabelInfo;
        //    list intfLabel {
        //        uses intfLabelInfo;
        //    }
        }
        output {
        //    leaf result { type string; }
        }
    }
}
