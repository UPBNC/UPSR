module upsrTunnel {
    yang-version 1;
    namespace "urn:opendaylight:params:xml:ns:yang:upsrTunnel";
    prefix "upsrTunnel";

    revision "2018-12-27" {
        description "Initial revision of upsrTunnel model";
    }

    grouping staticBfdInfo{
        leaf bdfType { type int32; }
        leaf bfdTimeoutTimes { type int32; }
        leaf bfdrxInterval { type int32; }
        leaf bfdtxInterval { type int32; }
        leaf discriminatorLocal { type string; }
        leaf discriminatorRemote { type string; }
    }

    grouping tunnelBfd {
        leaf bfdMultiplier { type string; }
        leaf bfdrxInterval { type string; }
        leaf bfdtxInterval { type string; }
        leaf localDiscriminator { type string; }
        leaf remoteDiscriminator { type string; }
    }
    grouping tunnelHop {
        leaf index { type string; }
        leaf ifAddress { type string; }
        leaf routerId { type string; }
        leaf adjlabel { type string; }
        leaf deviceName { type string; }
    }
    grouping tunnelInstance {
        leaf srcDevice { type string; }
        leaf srcRouterId { type string; }
        leaf tunnelId { type string; }
        leaf tunnelName { type string; }
        leaf destDevice { type string; }
        leaf destRouterId { type string; }
        leaf bandWidth { type string; }
        leaf serviceClass { type string; }
        leaf bfdType { type string; }
        container tunnelBfd { uses tunnelBfd; }
        container mainLspBfd { uses tunnelBfd; }
        container tunnelStaticBfd {uses tunnelBfd; }
        list mainPath { uses tunnelHop; }
        list backPath { uses tunnelHop; }
        leaf mainPathBand { type string; }
        leaf backPathBand { type string; }
    }
    grouping pingResultGroup {
        container pingResult {
            leaf packetSend { type string; }
            leaf packetRecv { type string; }
            leaf lossRatio { type string; }
            leaf rttValue { type string; }
        }
    }
    grouping traceResultGroup {
        container traceResult {
            leaf status { type string; }
            leaf errorType { type string; }
            list pathInfo {
                leaf index { type string; }
                leaf ifAddress { type string; }
            }
        }
    }
    rpc getTunnelInstances {
        input {
            leaf routerId { type string; }
            leaf tunnelName { type string; }
        }
        output {
            leaf result { type string; }
            list tunnelInstances {
                uses tunnelInstance;
            }
        }
    }
    rpc updateTunnelInstance {
        input {
            uses tunnelInstance;
        }
        output {
            leaf result { type string; }
        }
    }
    rpc createTunnelInstance {
        input {
            uses tunnelInstance;
        }
        output {
            leaf result { type string; }
        }
    }
    rpc deleteTunnelInstance {
        input {
            leaf routerId { type string; }
            leaf tunnelName { type string; }
        }
        output {
            leaf result { type string; }
        }
    }

    rpc traceTunnelInstance {
        input {
            leaf routerId { type string; }
            leaf tunnelName { type string; }
        }
        output {
            leaf result { type string; }
        }
    }

    rpc pingTunnelInstance {
        input {
            leaf routerId { type string; }
            leaf tunnelName { type string; }
            leaf lspPath { type string; }
        }
        output {
            leaf result { type string; }
            uses pingResultGroup;
        }
    }

    rpc detectTunnelPath{
        input {
            leaf routerId { type string; }
            leaf tunnelName { type string; }
            leaf lspPath { type string; }
        }
        output {
            leaf result { type string; }
            leaf tunnelName { type string; }
            uses pingResultGroup;
            uses traceResultGroup;
        }
    }

    rpc generateTunnelName{
        input {
            leaf routerId { type string; }
        }
        output {
            leaf result { type string; }
            leaf tunnelId { type string; }
            leaf tunnelName { type string; }
        }
    }

    rpc suggestTunnel {
        input {
            leaf srcRouterId { type string; }
            leaf dstRouterId { type string; }
        }
        output {
            leaf result { type string; }
            list candidateTunnel {
                uses tunnelInstance;
            }
        }
    }
}
