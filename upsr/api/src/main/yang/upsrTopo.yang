module upsrTopo {
    yang-version 1;
    namespace "urn:opendaylight:params:xml:ns:yang:upsrTopo";
    prefix "upsrTopo";

    revision "2018-11-19" {
        description "Initial revision of upsrTopo model";
    }
    import upsrSrLabel {
        prefix upsrSrLabel;
    }

    grouping nodeInfo {
        list nodes {
            leaf routerId { type string; }
            leaf srEnabled { type string; }
            leaf deviceName { type string; }
            uses upsrSrLabel:srGlobal;
            list deviceInterfaces {
                uses upsrSrLabel:srInterface;
            }
        }
    }

    grouping linkInfo {
        list links {
            leaf linkId { type string; }
            leaf linkStatus { type string; }
            container source {
                leaf routerId { type string; }
                leaf ifAddress { type string; }
                leaf adjlabel { type string; }
            }
            container dest {
                leaf routerId { type string; }
                leaf ifAddress { type string; }
                leaf adjlabel { type string; }
            }
        }
    }

    rpc getNodes {
        input {
            leaf routerId { type string; }
            leaf ifAddress { type string; }
        }
        output {
            uses nodeInfo;
        }
    }

    rpc getLinks {
        input {
            leaf linkId { type string; }
        }
        output {
            uses linkInfo;
        }
    }

    rpc getTopo {
        output {
            leaf result { type string; }
            uses nodeInfo;
            uses linkInfo;
        }
    }
}
